import FreeCAD as App
import Part
import Mesh
from FreeCAD import Base

# Create a new document or use the active one
doc = App.activeDocument() if App.activeDocument() else App.newDocument()


class SquareText():

    def __init__(self):
        print("SquareText created")

    font_5x3 = (
        (0, 0),         # 32 - 'Space'
        (23,),          # 33 - '!'
        (3, 0, 3),      # 34 - '"'
        (31, 10, 31),   # 35 - '#'
        (22, 31, 13),   # 36 - '$'
        (9, 4, 18),     # 37 - '%'
        (10, 21, 26),   # 38 - '&'
        (3,),           # 39
        (14, 17),       # 40 - '('
        (17, 14),       # 41 - ')'
        (10, 4, 10),    # 42 - '*'
        (4, 14, 4),     # 43 - '+'
        (16, 8),        # 44 - ','
        (4, 4, 4),      # 45 - '-'
        (16,),          # 46 - '.'
        (8, 4, 2),      # 47 - '/'
        (31, 17, 31),   # 48 - '0'
        (0, 31),        # 49 - '1'
        (29, 21, 23),   # 50 - '2'
        (17, 21, 31),   # 51 - '3'
        (7, 4, 31),     # 52 - '4'
        (23, 21, 29),   # 53 - '5'
        (31, 21, 29),   # 54 - '6'
        (1, 1, 31),     # 55 - '7'
        (31, 21, 31),   # 56 - '8'
        (23, 21, 31),   # 57 - '9'
        (10,),          # 58 - ':'
        (16, 10),       # 59 - ';'
        (4, 10, 17),    # 60 - '<'
        (10, 10, 10),   # 61 - '='
        (17, 10, 4),    # 62 - '>'
        (1, 21, 3),     # 63 - '?'
        (14, 21, 22),   # 64 - '@'
        (30, 5, 30),    # 65 - 'A'
        (31, 21, 10),   # 66 - 'B'
        (14, 17, 17),   # 67 - 'C'
        (31, 17, 14),   # 68 - 'D'
        (31, 21, 17),   # 69 - 'E'
        (31, 5, 1),     # 70 - 'F'
        (14, 17, 29),   # 71 - 'G'
        (31, 4, 31),    # 72 - 'H'
        (17, 31, 17),   # 73 - 'I'
        (8, 16, 15),    # 74 - 'J'
        (31, 4, 27),    # 75 - 'K'
        (31, 16, 16),   # 76 - 'L'
        (31, 2, 31),    # 77 - 'M'
        (31, 14, 31),   # 78 - 'N'
        (14, 17, 14),   # 79 - 'O'
        (31, 5, 2),     # 80 - 'P'
        (14, 25, 30),   # 81 - 'Q'
        (31, 5, 26),    # 82 - 'R'
        (18, 21, 9),    # 83 - 'S'
        (1, 31, 1),     # 84 - 'T'
        (31, 16, 31),   # 85 - 'U'
        (7, 24, 7),     # 86 - 'V'
        (15, 28, 15),   # 87 - 'W'
        (27, 4, 27),    # 88 - 'X'
        (3, 28, 3),     # 89 - 'Y'
        (25, 21, 19),   # 90 - 'Z'
        (31, 17),       # 91 - '['
        (2, 4, 8),      # 92 - '\'
        (17, 31),       # 93 - ']'
        (2, 1, 2),      # 94 - '^'
        (16, 16, 16),   # 95 - '_'
        (1, 2),         # 96 - '`'
        (12, 18, 28),   # 97 - 'a'
        (31, 18, 12),   # 98 - 'b'
        (12, 18, 18),   # 99 - 'c'
        (12, 18, 31),   # 100 - 'd'
        (12, 26, 20),   # 101 - 'e'
        (4, 31, 5),     # 102 - 'f'
        (20, 26, 12),   # 103 - 'g'
        (31, 2, 28),    # 104 - 'h'
        (29,),          # 105 - 'i'
        (16, 13),       # 106 - 'j'
        (31, 8, 20),    # 107 - 'k'
        (31,),          # 108 - 'l'
        (30, 6, 30),    # 109 - 'm'
        (30, 2, 28),    # 110 - 'n'
        (12, 18, 12),   # 111 - 'o'
        (30, 10, 4),    # 112 - 'p'
        (4, 10, 30),    # 113 - 'q'
        (30, 4),        # 114 - 'r'
        (20, 30, 10),   # 115 - 's'
        (4, 30, 4),     # 116 - 't'
        (14, 16, 30),   # 117 - 'u'
        (14, 16, 14),   # 118 - 'v'
        (14, 24, 14),   # 119 - 'w'
        (18, 12, 18),   # 120 - 'x'
        (22, 24, 14),   # 121 - 'y'
        (26, 30, 22),   # 122 - 'z'
        (4, 27, 17),    # 123 - '{'
        (27,),          # 124 - '|'
        (17, 27, 4),    # 125 - '}'
        (6, 2, 3),      # 126 - '~'
        (31, 31, 31) # 127 - 'Full Block'
    )

    def get_char_design(self,ch):
        ch_offset = ord(ch) - ord(' ')
        if ch_offset<0 or ch_offset>len(self.font_5x3):
            return None
        return self.font_5x3[ch_offset]

    def text_width_in_dots(self,text):

        print("Measuring:",text)

        result = 0

        if text == '':
            return 0

        ch_pos = 0

        while ch_pos < len(text):

            ch = text[ch_pos]

            print(ch)

            char_design = self.get_char_design(ch)

            if char_design == None:
                return None

            result = result + len(char_design) + 1
    
            ch_pos = ch_pos + 1

        return result
    
    def draw_text(self,text, x,y,z,width,depth,height):

        print("Building:",text)

        result = None

        if text == '':
            return

        ch_pos = 0

        while ch_pos < len(text):

            ch = text[ch_pos]

            print(ch)

            char_design = self.get_char_design(ch)

            if char_design == None:
                return

            char_design_length = len(char_design)
            column = 0

            while column < char_design_length:
                # display the character raster
                font_column =char_design[column]
                bit = 1
                yp = y + (5*depth)
                while(bit<32):
                    if font_column & bit:
                        pos = Base.Vector(x,yp,z)
                        dot = Part.makeBox(width,depth,height,pos)
                        if result==None:
                            result = dot
                        else:  
                            result=result.fuse(dot)

                    # move on to the next bit in the column
                    bit = bit + bit
                    # move onto the next pixel to draw
                    yp=yp-depth
                x = x + width
                column = column + 1

            # reached the end of displaying a character - move to the next one
            x = x + width
            ch_pos = ch_pos + 1
        return result
        

def squareTest():
    t = SquareText()
    l1 = t.draw_text("HULL",0,60,0,10,10,10)
    l2 = t.draw_text("CS50",0,0,0,10,10,10)
    logo = l1.fuse(l2)
    result = logo
    for i in range(0,25,5):
        x = i
        y = i
        z = i
        logo.translate(Base.Vector(x,y,z))
        result = result.fuse(logo)
        logo.translate(Base.Vector(-x,-y,-z))
    print("done")
    Part.show(result)
    Gui.SendMsgToActiveView("ViewFit")
    Gui.activeDocument().activeView().viewAxometric()




import os

dir = "C:/Users/rsmil/OneDrive/Hackspace Magazine/2024-04-15 Minox and 3D printing/Robs Minox Cassette/"

def ring(outerRadius,height, thickness,position=Base.Vector(0,0,0)):
    result = Part.makeCylinder(outerRadius,height)
    innerRadius = outerRadius - thickness
    result = result.cut(Part.makeCylinder(innerRadius,height))
    return result.translate(position)

def tetrahedron(size):
    # Define vertices
    vertices = [
        App.Vector(0, 0, 0),       # Vertex 0
        App.Vector(size, 0, 0),       # Vertex 1
        App.Vector(size*0.5, size*0.866, 0), # Vertex 2
        App.Vector(size*0.5, size*0.288, size*0.816) # Vertex 3
    ]
    
    # Create faces using the vertices
    faces = [
        Part.makePolygon([vertices[0], vertices[1], vertices[2], vertices[0]]),
        Part.makePolygon([vertices[0], vertices[1], vertices[3], vertices[0]]),
        Part.makePolygon([vertices[1], vertices[2], vertices[3], vertices[1]]),
        Part.makePolygon([vertices[2], vertices[0], vertices[3], vertices[2]])
    ]
    
    # Convert polygons to faces
    face_objects = [Part.Face(face) for face in faces]
    
    # Create a shell and then a solid from the faces
    shell = Part.makeShell(face_objects)
    solid = Part.makeSolid(shell)
    return solid


def cassette(outerRadius, rimHeight, baseThickness,rimThickness, holeRadius, boxWidth, boxDepth,slotDepth, hubRadius, hubHeight, filmHeight, filmGap,contanerSeparation,cassetteSlotDepth):
    result = []
    
    leftLid = Part.makeCylinder(outerRadius,baseThickness+rimHeight)
    box = Part.makeBox(boxWidth,boxDepth,rimHeight+baseThickness,Base.Vector(0,outerRadius-boxDepth,0))
    leftLid = leftLid.fuse(box)
    box = box.translate(Base.Vector(-rimThickness,-rimThickness,baseThickness))
    leftLid = leftLid.cut(box)
    boxCut = Part.makeBox(boxWidth,slotDepth,rimHeight,Base.Vector(0,outerRadius-(slotDepth+rimThickness),baseThickness))
    leftLid = leftLid.cut(boxCut)
    rimCut = Part.makeCylinder(outerRadius-rimThickness,rimHeight,Base.Vector(0,0,baseThickness))
    leftLid = leftLid.cut(rimCut)
    hub = Part.makeCylinder(hubRadius,hubHeight,Base.Vector(0,0,baseThickness))
    leftLid = leftLid.fuse(hub)
    result.append((leftLid,"leftLid"))

    rightLid = Part.makeCylinder(outerRadius,baseThickness+rimHeight)
    box = Part.makeBox(boxWidth,boxDepth,rimHeight+baseThickness,Base.Vector(-boxWidth,outerRadius-boxDepth,0))
    rightLid = rightLid.fuse(box)
    box = box.translate(Base.Vector(rimThickness,-rimThickness,baseThickness))
    rightLid = rightLid.cut(box)
    boxCut = Part.makeBox(boxWidth,slotDepth,rimHeight,Base.Vector(-boxWidth,outerRadius-(slotDepth+rimThickness),baseThickness))
    rightLid = rightLid.cut(boxCut)
    rimCut = Part.makeCylinder(outerRadius-rimThickness,rimHeight,Base.Vector(0,0,baseThickness))
    rightLid = rightLid.cut(rimCut)
    holeRim = Part.makeCylinder(holeRadius+rimThickness,rimHeight,Base.Vector(0,0,baseThickness))
    rightLid = rightLid.fuse(holeRim)
    holeCut = Part.makeCylinder(holeRadius,rimHeight+baseThickness,Base.Vector(0,0,0))
    rightLid = rightLid.cut(holeCut)
    result.append((rightLid,"rightLid"))

    holderBaseHeight = filmHeight + filmGap - rimHeight

    slotOffset=0.6

    leftHolder = Part.makeCylinder(outerRadius,holderBaseHeight+baseThickness)
    box = Part.makeBox(boxWidth,boxDepth,holderBaseHeight+baseThickness,Base.Vector(0,outerRadius-boxDepth,0))
    leftHolder = leftHolder.fuse(box)
    boxCut = Part.makeBox(boxWidth,cassetteSlotDepth,holderBaseHeight,Base.Vector(0,outerRadius-(slotDepth+(2*rimThickness))+slotOffset,baseThickness))
    leftHolder = leftHolder.cut(boxCut)
    rimCut = Part.makeCylinder(outerRadius-(2*rimThickness),holderBaseHeight,Base.Vector(0,0,baseThickness))
    leftHolder = leftHolder.cut(rimCut)

    leftHolderTop = Part.makeCylinder(outerRadius-rimThickness,rimHeight,Base.Vector(0,0, holderBaseHeight+baseThickness))
    box = Part.makeBox(boxWidth,boxDepth-(2*rimThickness),rimHeight,Base.Vector(-rimThickness,outerRadius-boxDepth+rimThickness,holderBaseHeight+baseThickness))
    leftHolderTop = leftHolderTop.fuse(box)
    boxCut = Part.makeBox(boxWidth,cassetteSlotDepth,rimHeight,Base.Vector(0,outerRadius-(slotDepth+(2*rimThickness))+slotOffset,holderBaseHeight+baseThickness))
    leftHolderTop = leftHolderTop.cut(boxCut)

    leftHolder = leftHolder.fuse(leftHolderTop)
    rimCut = Part.makeCylinder(outerRadius-(2*rimThickness),holderBaseHeight,Base.Vector(0,0,holderBaseHeight+baseThickness))
    leftHolder = leftHolder.cut(rimCut)

    rightHolder = Part.makeCylinder(outerRadius,holderBaseHeight+baseThickness)
    box = Part.makeBox(boxWidth,boxDepth,holderBaseHeight+baseThickness,Base.Vector(-boxWidth,outerRadius-boxDepth,0))
    rightHolder = rightHolder.fuse(box)
    boxCut = Part.makeBox(boxWidth,cassetteSlotDepth,holderBaseHeight,Base.Vector(-boxWidth,outerRadius-(slotDepth+(2*rimThickness))+slotOffset,baseThickness))
    rightHolder = rightHolder.cut(boxCut)
    rimCut = Part.makeCylinder(outerRadius-(2*rimThickness),holderBaseHeight,Base.Vector(0,0,baseThickness))
    rightHolder = rightHolder.cut(rimCut)

    rightHolderTop = Part.makeCylinder(outerRadius-rimThickness,rimHeight,Base.Vector(0,0, holderBaseHeight+baseThickness))
    box = Part.makeBox(boxWidth,boxDepth-(2*rimThickness),rimHeight,Base.Vector(-(boxWidth)+rimThickness,outerRadius-boxDepth+rimThickness,holderBaseHeight+baseThickness))
    rightHolderTop = rightHolderTop.fuse(box)
    boxCut = Part.makeBox(boxWidth,cassetteSlotDepth,rimHeight,Base.Vector(-boxWidth-rimThickness,outerRadius-(slotDepth+(2*rimThickness))+slotOffset,holderBaseHeight+baseThickness))
    rightHolderTop = rightHolderTop.cut(boxCut)

    rightHolder = rightHolder.fuse(rightHolderTop)
    rimCut = Part.makeCylinder(outerRadius-(2*rimThickness),holderBaseHeight,Base.Vector(0,0,holderBaseHeight+baseThickness))
    rightHolder = rightHolder.cut(rimCut)

    leftHolder.translate(Base.Vector(-contanerSeparation,0,0))

    cassette = leftHolder.fuse(rightHolder)

    link = Part.makeBox(contanerSeparation,6.0,0.3,Base.Vector(-(contanerSeparation+outerRadius/2.0),-1.5,0))

    t = SquareText()

    text = "MV2"
    dot_width = 0.5

    text_length = t.text_width_in_dots(text)*dot_width

    text_x = -(contanerSeparation/2.0)-(text_length/2.0)

    logo = t.draw_text(text=text,x=text_x,y=-0.8, z=0,width=dot_width,depth=0.5,height=3.0)

    link = link.cut(logo)

    cassette = cassette.fuse(link)

    result.append((cassette,"cassette"))

    # Now create the takeup spool
    
    takeupHeight = filmHeight
    takeupWallThickness = 0.4
    takeupBaseHeight = 0.2
    # This is the clearnce between the bottom part of the takeup and the rim in the lid
    takeupGap = 0.15
    # Calculate the radius of the block - based on the size of the hole in the lid and alowing for the wall thickness and 
    innerBlockRadius = holeRadius+rimThickness

    takeupRadius = innerBlockRadius + takeupGap + takeupWallThickness
    takeupCutRadius = innerBlockRadius + takeupGap
    
    takeupSpool = Part.makeCylinder(takeupRadius,takeupHeight)

    takeupSpoolCut = Part.makeCylinder(takeupCutRadius,takeupHeight,Base.Vector(0,0,takeupBaseHeight))
    takeupSpool=takeupSpool.cut(takeupSpoolCut)
    
    takeupPinHeight=1.0
    takeupPinDepth=1.0
    takeupPinWidth=1.0
    
    takeupPinX = takeupCutRadius-takeupPinWidth
    takeupPinY = -(takeupPinDepth/2.0)
    takeupPinZ = takeupBaseHeight
    
    takeupPinPos =  Base.Vector(takeupPinX, takeupPinY, takeupPinZ) 
    takeupPin = Part.makeBox(takeupPinWidth,takeupPinDepth, takeupPinHeight, takeupPinPos)
#    takeupPin = tetrahedron(takeupPinWidth)
    takeupShift = Base.Vector(0,0,0)
    
    takeupSpool = takeupSpool.fuse(takeupPin)
    takeupSpool.rotate(takeupShift,Base.Vector(0,0,1),120)
    takeupSpool = takeupSpool.fuse(takeupPin)
    
    takeupSpool.rotate(takeupShift,Base.Vector(0,0,1),120)
    takeupSpool = takeupSpool.fuse(takeupPin)
    
    result.append((takeupSpool,"takeupSpool"))


    return result

plasticThickness = 0.4
baseThickness = 0.3

lidRimHeight = 4.4
filmCylinderRadius = 17.23/2.0
lidHoleRadius = 4.65
lidBoxDepth=4.0
lidBoxWidth = 6.0
lidSlotDepth = 1.8
cassetteSlotDepth = 1.2
lidHubRadius = 8.7/2.0
lidHubHeight = 4.6

overallCassetteWidth = 44.31
baseHeight = 0.54
takeupSpoolDiameter = 10.57
filmHeight = 9.0
filmGap = 0.08
contanerSeparation = 27.35

cassetteItems = cassette(outerRadius=filmCylinderRadius,rimHeight=lidRimHeight,baseThickness=baseThickness,rimThickness=plasticThickness,holeRadius=lidHoleRadius,boxWidth=lidBoxWidth,boxDepth=lidBoxDepth,slotDepth=lidSlotDepth,hubRadius=lidHubRadius,hubHeight=lidHubHeight, filmHeight=filmHeight,filmGap=filmGap,contanerSeparation=contanerSeparation,cassetteSlotDepth=cassetteSlotDepth)

zPos=0
for item in cassetteItems:
    part = item[0]
    name = item[1]
    part.translate(Base.Vector(0,0,zPos))
    Part.show(part)
    part.exportStl(dir+name+".stl")
    zPos = zPos + 10

Gui.SendMsgToActiveView("ViewFit")
Gui.activeDocument().activeView().viewAxometric()
print("Run complete")
